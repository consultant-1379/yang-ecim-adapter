module "ericsson-lrat-enb-adapter" {
	yang-version 1.1;
	namespace "urn:rdns:com:ericsson:oammodel:ericsson-lrat-enb-adapter";
	prefix lrtadpt;

	import ericsson-yang-extensions { prefix "yexte"; }
	import ericsson-adapter-yang-extensions { prefix "ayexte"; }
	import ericsson-rme-sef-enb-adapter { prefix "rsefadpt"; }
        import ericsson-req-equip-enb-adapter { prefix "reqeqadpt"; }
        import ericsson-req-antenna-enb-adapter { prefix reqantadpt; }

	organization "Ericsson AB";
	contact "Contact Ericsson first line support";
	description "This module represents a subset of the eNodeB Lrat ECIM fragment to facilitate
		a predev engagement with customer.
		The data was broadly selected based on the following MOs
			- EUtranCellFDD
			- ENodeBFunction
			- LoadBalancingFunction
			- EUtranCellRelation
			- EUtranFreqRelation
			- CarrierAggregationFunction
			- QciProfilePredefined
			- QciProfileOperatorDefined
	        - SectorCarrier
		and the following features
			- Inter-frequency Load Balancing (IFLB)
			- Carrier Aggregation-Aware IFLB
			- Configurable SCell Priority
	        - Qos-Aware Scheduler

		Copyright (c) 2018 Ericsson AB. All rights reserved.
	";

    revision "2018-09-06" {
        description "Updated administrative-state, operational-state and availability-status
            to list eutran-cell-fdd.";
        yexte:version "3";
        yexte:release "1";
        yexte:correction "0";
    }

    revision "2018-08-20" {
        description "Updated sector-carrier with references to rf-branch due to rf-branch 
            being added to scope.";
        yexte:version "3";
        yexte:release "0";
        yexte:correction "0";
    }

    revision "2018-08-02" {
        description "Uses extensions from ericsson-yang-extensions.
            Remove instance-identifier example values that had no prefix.
            Changed equal_rate to equal-rate in descriptions.
            Removed underscores from enum values.";
        yexte:version "2";
        yexte:release "0";
        yexte:correction "0";
    }

	revision "2018-07-02" {
	    description "Adding support for SectorCarrier MO";
        yexte:version "1";
        yexte:release "1";
        yexte:correction "0";
	}

    revision "2018-06-26" {
	    description "Fixed range for leaf a5-threshold2-rsrp";
		yexte:version "1";
		yexte:release "0";
		yexte:correction "1";
	}

	revision "2018-05-14" {
	    description "Initial version based on ECIM Lrat fragment (17A)
	            release=8051 revision=R7E02 version=1";
		yexte:version "1";
		yexte:release "0";
		yexte:correction "0";
	}

	grouping plmn-identity {
		description "The ENodeB Public Land Mobile Network (PLMN) ID that forms
			part of the ENodeB Global ID used to identify the node over
			the S1 interface. Note: The value (MCC=001, MNC=01)
			indicates that the PLMN is not initiated. The value can not
			be used as a valid PLMN Identity.";
		
		leaf mcc {
			type uint-999;
			mandatory true;
			description "The MCC part of a PLMN identity used in the radio network.";
		}
		
		leaf mnc {
			type uint-999;
			mandatory true;
			description "The MNC part of a PLMN identity used in the radio network.";
		}
		
		leaf mnc-length {
			type uint8 {
				range "2..3";
			}
			mandatory true;
			description "The length of the MNC part of a PLMN identity used in the
				radio network.";
		}
	}
	
	typedef uint-63 {
                type uint8 {
                        range "0..63";
                }
        }
	
	typedef uint-100 {
		type uint8 {
			range "0..100";
		}
	}
	
	typedef uint-500 {
                type uint16 {
                       range "0..500";
                }
        }

	typedef uint-999 {
		type uint16 {
			range "0..999";
		}
	}

	typedef uint-1000 {
		type uint16 {
			range "0..1000";
		}
	}
	
	typedef uint-5000 {
		type uint16 {
			range "0..5000";
		}
	}
	
	typedef uint-16000 {
		type uint16 {
			range "0..16000";
		}
	}
	
	typedef uint-50000 {
		type uint16 {
			range "0..50000";
		}
	}
	
	typedef uint-150000 {
                type uint32 {
                        range "0..150000";
                }
        }
	
	typedef uint-1000000 {
		type uint32 {
			range "0..1000000";
		}
	}

	typedef channel-bandwidth-type {
		type uint16 {
			range "1400|3000|5000|10000|15000|20000";
		}
		units "kHz";
		default 10000;
	}
	
	typedef offset-freq-type {
	    type int8 {
                range "-24|-22|-20|-18|-16|-14|-12|-10|-8|-6..6|8|10|12|14|16|18|20|22|24";
            }
	    units "dB";
	}
	
	typedef priority-type {
	    type uint8 {
	        range "1..14";
	    }
	}
	
	typedef relative-priority-type {
	    type uint16 {
                range "1..65535";
            }
	}

	typedef abs-prio-override-type {
        type enumeration {
            enum no-override {
                value 0;
                description "The default priority level is used in scheduling.";
            }
            enum hi-prio-override {
                value 1;
                description "The default priority level used in scheduling is always overridden;
                    instead the priorities assigned to the QCIs are always used.
                    These QCI priorities are higher (more important) than the default priority
                    level.";
            }
        }
    }

    typedef avail-status {
        type enumeration {
            enum in-test {
                value 0;
                description "The resource is undergoing a test procedure.
                    If the administrative state is locked or shutting down,
                    normal users are prevented from using the resource.";
            }
            enum failed {
                value 1;
                description "The resource has an internal fault that prevents it from operating.";
            }
            enum power-off {
                value 2;
                description "The resource requires power to be applied and is not powered on.";
            }
            enum off-line {
                value 3;
                description "The resource requires a routine operation to be performed.
                    This routine operation is to place the resource online and make it available
                    for use. The operation may be manual or automatic, or both.
                    The operational state is disabled.";
            }
            enum off-duty {
                value 4;
                description "The resource has been made inactive by an internal control process.";
            }
            enum dependency {
                value 5;
                description "The resource cannot operate because some other resource on which it depends
                    is unavailable.";
            }
            enum degraded {
                value 6;
                description "The service available from the resource is degraded in some respect.";
            }
            enum not-installed {
                value 7;
                description "The resource represented by the managed object is not present, or is incomplete.";
            }
            enum log-full {
                value 8;
                description "Indicates a log full condition.
                    The semantics are defined in CCITT Rec. X.735 | ISO/IEC 10164-6.";
            }
            enum dependency-locked {
                value 9;
                description "The administrative state of a resource that this resource depends on is locked.
                    or the availability status of the other resource is dependency locked.";
            }
            enum dependency-failed {
                value 10;
                description "The availability status of a resource that this resource depends
                    on is failed or dependency failed.";
            }
            enum dependency-shuttingdown {
                value 11;
                description "The administrative state of a resource that this resource
                    depends on is shutting down or the availability status of the other
                    resource is dependency shutting down.";
            }
        }
    }

    typedef dl-calibration-method {
        type enumeration {
            enum none {
                value 0;
                description "No antenna calibration method.";
            }
            enum internal {
                value 1;
                description "Internal antenna calibration method.";
            }
        }
    }

    typedef dl-calibration-status-type {
        type enumeration {
            enum inactive {
                value 0;
                description "Downlink antenna calibration is not activated.";
            }
            enum converging {
                value 1;
                description "Downlink antenna calibration is converging.";
            }
            enum calibrated {
                value 2;
                description "Downlink antenna calibration is finished with success.";
            }
            enum failed {
                value 3;
                description "Downlink antenna calibration has failed.";
            }
        }
    }

	typedef load-balancing-type {
		type enumeration {
			enum not-allowed {
				value 0;
			}
			enum allowed {
				value 1;
			}
			enum offload {
				value 2;
			}
			enum ifo-and-iflb {
				value 3;
				description "Cell is allowed for both offload and load balancing 
					actions.";
			}
		}
	}
	
	typedef lb-qci-profile-handling-type {
		type enumeration {
			enum allowed {
				value 0;
				description "If a QCI profile is configured as ALLOWED then a UE may use
					it (but does not have to) in order to qualify for load
					balancing to the target frequency.";
			}
			enum forbidden {
				value 1;
				description "If a QCI profile is configured as FORBIDDEN then UEs using
					it are not qualified for load balancing to the target
					frequency.";
			}
			enum required {
				value 2;
				description "If one or more QCI profiles are configured as REQUIRED then
					only UEs using one or more of them are qualified for load
					balancing to the target frequency.";
			}
		}
	}

    typedef oper-state {
        type enumeration {
            enum disabled {
                value 0;
                description "The resource is totally inoperable.";
            }
            enum enabled {
                value 1;
                description "The resource is partially or fully operable.";
            }
        }
    }
    
    typedef radio-operating-mode {
        type enumeration {
            enum default {
                value 0;
                description "Radio is requested to be at the default operating mode.";
            }
            enum qam-64-boost {
                value 1;
                description "Radio is requested to be at an operating mode to achieve good throughput
                    performance when the highest modulation in DL is 64 QAM.";
            }
            enum qam-256-boost {
                value 2;
                description "Radio is requested to be at an operating mode to achieve good throughput
                    performance when the highest modulation in DL is 256 QAM.";
            }
            enum max-power-class {
                value 3;
                description "Radio is requested to be at the highest power level of the
                    power amplifier.";
            }
        }
    }

	typedef resource-allocation-strategy-type {
        type enumeration {
            enum resource-fair {
                value 0;
                description "Indicates that the resource allocation strategy is resource fair in frequency.";
            }
            enum frequency-selective {
                value 1;
                description "Indicates that the resource allocation strategy is frequency selective.";
            }
        }
    }
	
	typedef resource-type-type {
	    type enumeration {
	        enum non-gbr {
	            value 0;
	            description "Indicates the resource type of a QCI is Non-GBR type.";
	        }
	        enum gbr {
	            value 1;
	            description "Indicates the resource type of a QCI is GBR type.";
	        }
	    }
	}

	typedef s-cell-selection-mode-type {
		type enumeration {
			enum ack-sequential-scell-selection {
				value 0;
				description "A1 measurement configured at selection of secondary cell.
				    Configures one secondary cell at a time.";
			}
			enum un-ack-simultaneous-scell-selection {
				value 1;
				description "No A1 measurement configured at selection of secondary cell.
					Configures one or more secondary cells at a time at initial
					configuration.";
			}
			enum ack-simultaneous-scell-selection {
				value 2;
				description "A1 measurement configured at selection of secondary cell.
				    Configures one or more secondary cells at a time at initial
				    configuration.";
			}
		}
	}
	
	typedef scheduling-algorithm-type {
	    type enumeration {
	        enum resource-fair {
	            value 0;
	        }
	        enum equal-rate {
	            value 1;
	        }
	        enum proportional-fair-high {
	            value 2;
	        }
	        enum proportional-fair-medium {
                value 3;
            }
	        enum proportional-fair-low {
                value 4;
            }
	        enum maximum-c-over-i {
                value 5;
            }
	        enum delay-based {
                value 6;
            }
	    }
	}
	
	typedef service-type-type {
        type enumeration {
            enum undefined {
                value 0;
                description "No service defined";
            }
            enum voip {
                value 1;
                description "VoIP";
            }
            enum ims-signaling {
                value 2;
                description "Indicates that the bearer is used for IMS signaling.";
            }
        }
    }
	
	typedef srs-allocation-strategy-type {
        type enumeration {
            enum deactivated {
                value 0;
                description "Indicates the SRS allocation strategy is to have SRS disabled.";
            }
            enum activated {
                value 1;
                description "Indicates the SRS allocation strategy is to have SRS enabled.";
            }
        }
    }

	typedef dynamic-s-cell-selection-method-type {
		type enumeration {
			enum round-robin {
				value 0;
				description "Secondary cell selection order determined using a round robin
					selection of secondary cell candidates.
					
					Dependencies: Only applicable if Configurable SCell Priority, FAJ 121 4701
					is active";
			}
			enum prioritized {
				value 1;
				description "Secondary cell selection order determined using a prioritized
					selection of secondary cell candidates based on frequency prioritization.
					
					Dependencies: Only applicable if Configurable SCell Priority, FAJ 121 4701
					is active";
			}
			enum prioritized-automatic {
				value 2;
				description "Secondary cell selection prioritizes carriers with best combination
					of bandwidth and potential number of layers.
					
					Dependencies: Only applicable if Automatic SCell Priority, FAJ 121 4734
					is active.";
			}
		}
	}

	typedef ca-preference-type {
		type enumeration {
			enum none {
				value 0;
				description "No preference between downlink and uplink carrier
					aggregation.";
			}
			enum dl {
				value 1;
				description "Downlink carrier aggregation is preferred over uplink
					carrier aggregation.";
			}
			enum ul {
				value 2;
				description "Uplink carrier aggregation is preferred over downlink
					carrier aggregation.";
			}
		}
	}
	
	typedef s-cell-candidate-type {
		type enumeration {
			enum not-allowed {
				value 0;
				description "The cell indicated by the value of parameter cellrelation
					must not be used as secondary component carrier (SCell) for UE using this
					cell as their primary component carrier (PCell).";
			}
			enum allowed {
				value 1;
				description "The cell indicated by the value of parameter cellrelation can be
					used as a secondary cell CC for UEs that use this cell as their primary
					cell CC for both UL and DL.";
			}
			enum auto {
				value 2;
				description "Same as not-allowed.";
			}
			enum only-allowed-for-dl {
				value 3;
				description "The current cell is allowed to use the cell indicated by the
					cell relation as a secondary cell candidate for DL CA only. This secondary
					cell cannot be used for UL CA. UL CA performance degradation in secondary
					cell occurs if the antenna of the secondary cell is placed more than
					300 meters from the antenna from the primary cell. It is recommended that
					this parameter is set for cases where this can occur.";
			}
		}
	}
	
	typedef supported-coverage-type {
		type enumeration {
			enum none {
				value 0;
				description "There is no coverage relation (e.g. the cells only partially overlap).";
			}
			enum covers {
				value 1;
				description "The related cell covers the eutran cell.";
			}
			enum overlap {
				value 2;
				description "The related cell and the eutran cell has approximately the same coverage area.";
			}
			enum contained-in {
				value 3;
				description "The related cell is contained in the eutran cell.";
			}
		}
	}

        typedef adm-state {
                type enumeration {
                        enum locked {
                                  value 0;
                                  description "The resource is administratively prohibited from performing services
                                      for its users.";
                        }
                        enum unlocked {
                                  value 1;
                                  description "The resource is administratively permitted to perform services
                                      for its users.
                                      This is independent of its inherent operability.";
                        }
                        enum shuttingdown {
                                  value 2;
                                  description "Use of the resource is administratively permitted to existing instances
                                      of use only.
                                      While the system remains in the shutting down state the manager may at any time
                                      cause the resource to revert to the locked state.";
                        }
                }
        }

	container enodeb-function {
		yexte:is-system-created;

		leaf enb-id {
			type int32 {
				range "-1..1048575";
			}
			default -1;
			yexte:takes-effect "Next restart";
			description "The ENodeB ID that forms part of the Cell Global Identity,
				and is also used to identify the node over the S1 interface.
				
				Takes effect: Next restart";
		}

		container enodeb-plmn-id {
			description "Takes effect: Next restart";
			yexte:takes-effect "Next restart";
			uses plmn-identity;
		}
		
		container qci-table {
			description "Contains mapping from QCIs to parameters that has impact on
				QoS for DRBs.";
			yexte:is-system-created;

			list qci-profile-predefined {
				key "id";
				unique "qci";
				min-elements 10;
				max-elements 10;
				description "Contains bearer-level QoS configuration. Each
					list entry corresponds to a standardized
					QCI as described in TS 23.203, except for a default QCI
					profile activated whenever a profile related to a specific
					QCI is not defined.";
				yexte:is-system-created;

				leaf id {
					type string {
						pattern 'default|qci[1-9]';
					}
					description "The ids created by system are qci1, qci2, .. qci9, default.";
				}
				
				leaf qci {
                    type uint8 {
                        range "0..9";
                    }
                    config false;
                    description "Quality of Service Class Indicator (QCI) as defined in 3GPP
                        TS 23.203 (Release 8).
                        
                        Special value: 0 refers to a default QCI profile activated whenever a profile
                        related to a specific QCI has not been defined.";
                }

				leaf qci-subscription-quanta {
					type uint-50000;
					default 1;
					description "Normalized subscription quantity associated with the
						specific the QCI. Specifies the subscription cost of a
						bearer with this predefined profile. The subscription cost
						is used for traffic load balancing purposes.
						
						Traffic disturbance: Changing this leaf can cause loss of traffic";
					yexte:disturbances "Changing this leaf can cause loss of traffic";
				}
				
				leaf dscp {
                    type uint-63;
                    mandatory true;
                    description "The Differentiated Services Code Point for a Quality of Service Class
                        Indicator (QCI). This corresponds to mappings from RAN QoS to Transport
                        Network QoS.
                        
                        Takes effect: New connection";
                    yexte:takes-effect "New connection";
                }
                
                leaf logical-channel-group-ref {
                    type leafref {
                        path "../../logical-channel-group/id";
                    }
                    mandatory true;
                    description "Refers to an instance of LogicalChannelGroup. Assigns a Logical
                        Channel Group to a Quality of Service Class Indicator (QCI).
                        
                        Takes effect: New connection";
                    yexte:takes-effect "New connection";
                }
                
                leaf priority {
                    type priority-type;
                    mandatory true;
                    description "Quality of Service Class Indicator (QCI)-related priority as defined
                        in 3GPP TS 23.203 (Release 8).

                        Traffic disturbance: Changing this leaf can cause loss of traffic.
                        Takes effect: New connection";
                    yexte:disturbances "Changing this leaf can cause loss of traffic.";
                    yexte:takes-effect "New connection";
                }

                leaf resource-type {
                    type resource-type-type;
                    config false;
                    description "Indicates if the resource type of the Quality of Service Class Indicator (QCI)
                        is Guaranteed Bit Rate (GBR) or non-GBR as defined in 3GPP TS 23.203.

                        Takes effect: Object unlocked";
                    yexte:takes-effect "Object unlocked"; // Which Object?
                }

                leaf scheduling-algorithm {
                    type scheduling-algorithm-type;
                    default resource-fair;
                    description "Specifies which scheduling algorithm is to be used for a certain QCI.

                        Dependencies: Only applicable if QoS Aware Scheduler, FAJ 121 0859
                        is active. The value delay-based can only be used if the leaf
                        service-type has value voip.      
                        Takes-effect: New connection";
                    yexte:dependencies "Only applicable if QoS Aware Scheduler, FAJ 121 0859
                        is active. The value delay-based can only be used if the leaf
                        service-type has value voip.";
                    yexte:takes-effect "New connection";
                }
                
                leaf abs-prio-override {
                    type abs-prio-override-type;
                    default no-override;
                    description "Indicates if the data radio bearer is subject to Absolute Priority Override.
                        
                        Dependencies: Only applicable if QoS Aware Scheduler, FAJ 121 0859 is active.
                        Takes-effect: New connection";
                    yexte:dependencies "Only applicable if QoS Aware Scheduler, FAJ 121 0859 is active.";
                    yexte:takes-effect "New connection";
                }
                
                leaf dl-max-waiting-time {
                    type uint-500;
                    units "ms";
                    default 0;
                    description "The scheduler attempts to achieve dl-max-waiting-time for DL bearers
                        before giving any DL bearer a higher priority.
                        Value 0 means that the higher priority is never applied.
                        Must be set to a similar or slightly shorter value than the pdb.
                        Setting too low a value can affect other services with higher priority.
                        For more information about pdb refer to TS 23.203.
                        
                        Dependencies: Only used for Resource Fair Scheduling algorithm. Only applicable
                        if Advanced Differentiation for Resource Fair Scheduler, FAJ 121 4415 is active.
                        Disturbances: Changing this leaf can affect performance of all data bearers.
                        A value that is set too low can affect other services with higher priority.
                        A value that is set too high can cause Dynamic UE Admission Control to fail
                        in keeping the cell stable at overload.
                        Takes-effect: New connection";
                    yexte:dependencies "Only used for Resource Fair Scheduling algorithm. Only applicable
                        if Advanced Differentiation for Resource Fair Scheduler, FAJ 121 4415 is active.";
                    yexte:disturbances "Changing this leaf can affect performance of all data bearers.
                        A value that is set too low can affect other services with higher priority.
                        A value that is set too high can cause Dynamic UE Admission Control to fail
                        in keeping the cell stable at overload.";
                    yexte:takes-effect "New connection";
                }
                
                leaf dl-min-bit-rate {
                    type uint-150000;
                    units "kbps";
                    default 0;
                    description "The scheduler will attempt to achieve minbitrate for all bearers
                        before giving any user a higher rate.
                        Value 0 means that the minRate scheduler is not used.
                        
                        Dependencies: This parameter will only be used if one of the following
                        Proportional Fair scheduling algorithms has been selected
                            - maximum-c-over-i
                            - proportional-fair-low
                            - proportional-fair-medium
                            - proportional-fair-high
                            - equal-rate.
                        Only applicable if QoS Aware Scheduler, FAJ 121 0859 is active.
                        Takes-effect: New connection";
                    yexte:dependencies "This parameter will only be used if one of the following
                        Proportional Fair scheduling algorithms has been selected
                            - maximum-c-over-i
                            - proportional-fair-low
                            - proportional-fair-medium
                            - proportional-fair-high
                            - equal-rate.
                        Only applicable if QoS Aware Scheduler, FAJ 121 0859 is active.";
                    yexte:takes-effect "New connection"; // Disturbances is described in 17Q3.5 CPI ?????
                }
                
                leaf dl-resource-allocation-strategy {
                    type resource-allocation-strategy-type;
                    default resource-fair;
                    description "Defines the downlink resource allocation strategy of the
                        QoS Class Identifier (QCI).
                        
                        Dependencies: Only applicable if Downlink Frequency Selective Scheduling, FAJ 121 2053 and
                        QoS Aware Scheduler, FAJ 121 0859 are active.
                        Takes-effect: New connection";
                    yexte:dependencies "Only applicable if Downlink Frequency Selective Scheduling, FAJ 121 2053 and
                        QoS Aware Scheduler, FAJ 121 0859 are active.";
                    yexte:takes-effect "New connection";
                }
                
                leaf pdb {
                    type uint-500;
                    units "ms";
                    default 0;
                    description "The contribution from eNodeB to the Packet Delay Budget (PDB) for a QCI.
                        Packet delays outside eNodeB e.g. in the transport network are excluded.
                        For more information about PDB refer to TS 23.203
                        
                        Dependencies: Only applicable if QoS Aware Scheduler, FAJ 121 0859 is active.
                        Takes-effect: Cell lock/unlock";
                    yexte:dependencies "Only applicable if QoS Aware Scheduler, FAJ 121 0859 is active.";
                    yexte:takes-effect "Cell lock/unlock";
                }
                
                leaf relative-priority {
                    type relative-priority-type;
                    default 1;
                    description "The relative priority associated with a QCI.
                        
                        Dependencies: Only applicable if QoS Aware Scheduler, FAJ 121 0859,
                        Minimum Rate Proportional Fair Scheduler FAJ 121 0920 and
                        Relative Priority Scheduling, FAJ 121 2037 are active.
                        Takes-effect: New connection";
                    yexte:dependencies "Only applicable if QoS Aware Scheduler, FAJ 121 0859,
                        Minimum Rate Proportional Fair Scheduler FAJ 121 0920 and
                        Relative Priority Scheduling, FAJ 121 2037 are active.";
                    yexte:takes-effect "New connection";
                }
                
                leaf resource-allocation-strategy {
                    type resource-allocation-strategy-type;
                    default resource-fair;
                    description "Defines the resource allocation strategy of the QoS Class Identifier (QCI).
                        
                        Dependencies: Only applicable if QoS Aware Scheduler, FAJ 121 0859 and
                        Uplink Frequency Selective Scheduling, FAJ 121 1799 are active.
                        Takes-effect: New connection";
                    yexte:dependencies "Only applicable if QoS Aware Scheduler, FAJ 121 0859 and
                        Uplink Frequency Selective Scheduling, FAJ 121 1799 are active.";
                    yexte:takes-effect "New connection";
                }
                
                leaf service-type {
                    type service-type-type;
                    default undefined;
                    description "Indicates the service that the bearer is used for.
                        
                        Dependencies: Only applicable if QoS Aware Scheduler, FAJ 121 0859 is active.
                        Takes-effect: Cell lock/unlock";
                    yexte:dependencies "Only applicable if QoS Aware Scheduler, FAJ 121 0859 is active.";
                    yexte:takes-effect "Cell lock/unlock";
                }
                
                leaf srs-allocation-strategy {
                    type srs-allocation-strategy-type;
                    default deactivated;
                    description "If the leaf srs-allocation-strategy in the QoS configuration for a Data radio
                        Bearer assigned to a UE is set to activated, then an attempt is made to allocate
                        sounding for a UE. If several Data Radio Bearers are setup towards the UE with
                        different QoS configurations, and the QoS configurations has different
                        QCI parameter, an algorithm using the priority parameter in
                        the QoS configuration, will resolve which QoS configuration that
                        will define sounding
                        
                        Dependencies: Only applicable if QoS Aware Scheduler, FAJ 121 0859 and
                        Frequency Selective Scheduling are active.
                        Takes-effect: New connection";
                    yexte:dependencies "Only applicable if QoS Aware Scheduler, FAJ 121 0859 and
                        Frequency Selective Scheduling are active.";
                    yexte:takes-effect "New connection";
                }
                
                leaf ul-max-waiting-time {
                    type uint-500;
                    units "ms";
                    default 0;
                    description "The scheduler attempts to achieve ul-max-waiting-time for UL bearers
                        before giving any UL bearer a higher priority.
                        Value 0 means that the higher priority is never applied.
                        Must be set to a similar or slightly shorter value than the pdb.
                        Setting too low a value can affect other services with higher priority.
                        For more information about pdb refer to TS 23.203.
                        
                        Dependencies: Only used for Resource Fair Scheduling algorithm. Only applicable
                        if Advanced Differentiation for Resource Fair Scheduler, FAJ 121 4415 is active.
                        Disturbances: Changing this leaf can affect performance of all data bearers.
                        A value that is set too low can affect other services with higher priority.
                        A value that is set too high can cause Dynamic UE Admission Control to fail
                        in keeping the cell stable at overload.
                        Takes-effect: New connection";
                    yexte:dependencies "Only used for Resource Fair Scheduling algorithm. Only applicable
                        if Advanced Differentiation for Resource Fair Scheduler, FAJ 121 4415 is active.";
                    yexte:disturbances "Changing this leaf can affect performance of all data bearers.
                        A value that is set too low can affect other services with higher priority.
                        A value that is set too high can cause Dynamic UE Admission Control to fail
                        in keeping the cell stable at overload.";
                    yexte:takes-effect "New connection";
                }
                
                leaf ul-min-bit-rate {
                    type uint32 {
                        range "0..75000";
                    }
                    units "kbps";
                    default 0;
                    description "The scheduler will attempt to achieve minbitrate for all bearers
                        before giving any user a higher rate.
                        Value 0 means that the minRate scheduler is not used.
                        
                        Dependencies: This parameter will only be used if one of the following
                        Proportional Fair scheduling algorithms has been selected
                            - maximum-c-over-i
                            - proportional-fair-low
                            - proportional-fair-medium
                            - proportional-fair-high
                            - equal-rate.
                        Only applicable if QoS Aware Scheduler, FAJ 121 0859 is active.
                        Takes-effect: New connection";
                    yexte:dependencies "This parameter will only be used if one of the following
                        Proportional Fair scheduling algorithms has been selected
                            - maximum-c-over-i
                            - proportional-fair-low
                            - proportional-fair-medium
                            - proportional-fair-high
                            - equal-rate.
                        Only applicable if QoS Aware Scheduler, FAJ 121 0859 is active.";
                    yexte:takes-effect "New connection"; // Disturbances is described in 17Q3.5 CPI ?????
                }

			}

			list qci-profile-operator-defined {
				key "id";
				unique "qci";
				max-elements 9;
				description "Contains bearer-level QoS configuration. Each list entry
					corresponds to a unique operator defined QCI number within the range 10-255.
					
					Dependencies: Only applicable when feature Operator Defined QCI, FAJ 121 1892
					is active";
				yexte:dependencies "Only applicable when feature Operator Defined QCI, FAJ 121 1892
                    is active";

				leaf id {
                    type string;
                    description "A user friendly identifier for the qci profile";
                }
				
				leaf qci {
					type uint8 {
						range "10..255";
					}
					mandatory true;
					description "Quality of Service Class Indicator (QCI) as defined in 3GPP
						TS 23.203 (Release 8).
						
						Takes effect: Object unlocked";
					ayexte:restricted;
					yexte:takes-effect "Object unlocked";
				}

				leaf qci-subscription-quanta {
					type uint-50000;
					default 1;
					description "Normalized subscription quantity associated with the
						specific QCI. Specifies the subscription cost of a
						bearer with this predefined profile. The subscription cost
						is used for traffic load balancing purposes.
						
						Traffic disturbance: Changing this leaf can cause loss of traffic";
					yexte:disturbances "Changing this leaf can cause loss of traffic";
				}
				
				leaf dscp {
				    type uint-63;
				    mandatory true;
				    description "The Differentiated Services Code Point for a Quality of Service Class
				        Indicator (QCI). This corresponds to mappings from RAN QoS to Transport
				        Network QoS.
				        
				        Takes effect: New connection";
				    yexte:takes-effect "New connection";
				}
				
				leaf logical-channel-group-ref {
				    type leafref {
				        path "../../logical-channel-group/id";
				    }
                    mandatory true;
                    description "Refers to an instance of LogicalChannelGroup. Assigns a Logical
                        Channel Group to a Quality of Service Class Indicator (QCI).
                        
                        Takes effect: New connection";
                    yexte:takes-effect "New connection";
				}
				
				leaf priority {
				    type priority-type;
				    mandatory true;
				    description "Quality of Service Class Indicator (QCI)-related priority as defined
				        in 3GPP TS 23.203 (Release 8).
				        
				        Traffic disturbance: Changing this leaf can cause loss of traffic.
				        Takes effect: New connection";
				    yexte:disturbances "Changing this leaf can cause loss of traffic.";
				    yexte:takes-effect "New connection";
				}
				
				leaf resource-type {
				    type resource-type-type;
				    mandatory true;
				    description "Indicates if the resource type of the Quality of Service Class Indicator (QCI)
				        is Guaranteed Bit Rate (GBR) or non-GBR as defined in 3GPP TS 23.203.
				        
				        Takes effect: Object unlocked";
				    ayexte:restricted;
				    yexte:takes-effect "Object unlocked"; // Which Object?
				}
				
				leaf scheduling-algorithm {
				    type scheduling-algorithm-type;
				    default resource-fair;
				    description "Specifies which scheduling algorithm is to be used for a certain QCI.
				        
				        Dependencies: Only applicable if QoS Aware Scheduler, FAJ 121 0859
                        is active. The value delay-based can only be used if the leaf
                        service-type has value voip.      
				        Takes-effect: New connection";
				    yexte:dependencies "Only applicable if QoS Aware Scheduler, FAJ 121 0859
                        is active. The value delay-based can only be used if the leaf
				        service-type has value voip.";
				    yexte:takes-effect "New connection";
				}
				
				leaf abs-prio-override {
				    type abs-prio-override-type;
				    default no-override;
				    description "Indicates if the data radio bearer is subject to Absolute Priority Override.
				        
				        Dependencies: Only applicable if QoS Aware Scheduler, FAJ 121 0859 is active.
				        Takes-effect: New connection";
				    yexte:dependencies "Only applicable if QoS Aware Scheduler, FAJ 121 0859 is active.";
				    yexte:takes-effect "New connection";
				}
				
				leaf dl-max-waiting-time {
				    type uint-500;
				    units "ms";
				    default 0;
				    description "The scheduler attempts to achieve dl-max-waiting-time for DL bearers
				        before giving any DL bearer a higher priority.
				        Value 0 means that the higher priority is never applied.
				        Must be set to a similar or slightly shorter value than the pdb.
				        Setting too low a value can affect other services with higher priority.
				        For more information about pdb refer to TS 23.203.
				        
				        Dependencies: Only used for Resource Fair Scheduling algorithm. Only applicable
				        if Advanced Differentiation for Resource Fair Scheduler, FAJ 121 4415 is active.
				        Disturbances: Changing this leaf can affect performance of all data bearers.
                        A value that is set too low can affect other services with higher priority.
                        A value that is set too high can cause Dynamic UE Admission Control to fail
                        in keeping the cell stable at overload.
				        Takes-effect: New connection";
				    yexte:dependencies "Only used for Resource Fair Scheduling algorithm. Only applicable
				        if Advanced Differentiation for Resource Fair Scheduler, FAJ 121 4415 is active.";
				    yexte:disturbances "Changing this leaf can affect performance of all data bearers.
				        A value that is set too low can affect other services with higher priority.
				        A value that is set too high can cause Dynamic UE Admission Control to fail
				        in keeping the cell stable at overload.";
				    yexte:takes-effect "New connection";
				}
				
				leaf dl-min-bit-rate {
				    type uint-150000;
				    units "kbps";
                    default 0;
                    description "The scheduler will attempt to achieve minbitrate for all bearers
                        before giving any user a higher rate.
                        Value 0 means that the minRate scheduler is not used.
                        
                        Dependencies: This parameter will only be used if one of the following
                        Proportional Fair scheduling algorithms has been selected
                            - maximum-c-over-i
                            - proportional-fair-low
                            - proportional-fair-medium
                            - proportional-fair-high
                            - equal-rate.
                        Only applicable if QoS Aware Scheduler, FAJ 121 0859 is active.
                        Takes-effect: New connection";
                    yexte:dependencies "This parameter will only be used if one of the following
                        Proportional Fair scheduling algorithms has been selected
                            - maximum-c-over-i
                            - proportional-fair-low
                            - proportional-fair-medium
                            - proportional-fair-high
                            - equal-rate.
                        Only applicable if QoS Aware Scheduler, FAJ 121 0859 is active.";
                    yexte:takes-effect "New connection"; // Disturbances is described in 17Q3.5 CPI ?????
				}
				
				leaf dl-resource-allocation-strategy {
				    type resource-allocation-strategy-type;
				    default resource-fair;
				    description "Defines the downlink resource allocation strategy of the
				        QoS Class Identifier (QCI).
				        
				        Dependencies: Only applicable if Downlink Frequency Selective Scheduling, FAJ 121 2053 and
                        QoS Aware Scheduler, FAJ 121 0859 are active.
				        Takes-effect: New connection";
				    yexte:dependencies "Only applicable if Downlink Frequency Selective Scheduling, FAJ 121 2053 and
				        QoS Aware Scheduler, FAJ 121 0859 are active.";
                    yexte:takes-effect "New connection";
				}
				
				leaf pdb {
				    type uint-500;
				    units "ms";
				    default 80;
				    description "The contribution from eNodeB to the Packet Delay Budget (PDB) for a QCI.
				        Packet delays outside eNodeB e.g. in the transport network are excluded.
				        For more information about PDB refer to TS 23.203
				        
				        Dependencies: Only applicable if QoS Aware Scheduler, FAJ 121 0859 is active.
				        Takes-effect: Cell lock/unlock";
				    yexte:dependencies "Only applicable if QoS Aware Scheduler, FAJ 121 0859 is active.";
				    yexte:takes-effect "Cell lock/unlock";
				}
				
				leaf relative-priority {
				    type relative-priority-type;
				    default 1;
				    description "The relative priority associated with a QCI.
				        
				        Dependencies: Only applicable if QoS Aware Scheduler, FAJ 121 0859,
                        Minimum Rate Proportional Fair Scheduler FAJ 121 0920 and
                        Relative Priority Scheduling, FAJ 121 2037 are active.
				        Takes-effect: New connection";
				    yexte:dependencies "Only applicable if QoS Aware Scheduler, FAJ 121 0859,
				        Minimum Rate Proportional Fair Scheduler FAJ 121 0920 and
				        Relative Priority Scheduling, FAJ 121 2037 are active.";
                    yexte:takes-effect "New connection";
				}
				
				leaf resource-allocation-strategy {
				    type resource-allocation-strategy-type;
				    default resource-fair;
				    description "Defines the resource allocation strategy of the QoS Class Identifier (QCI).
				        
				        Dependencies: Only applicable if QoS Aware Scheduler, FAJ 121 0859 is active.
				        Takes-effect: New connection";
				    yexte:dependencies "Only applicable if QoS Aware Scheduler, FAJ 121 0859 is active.";
                    yexte:takes-effect "New connection";
				}
 				
				leaf service-type {
				    type service-type-type;
				    default undefined;
				    description "Indicates the service that the bearer is used for.
				        
				        Dependencies: Only applicable if QoS Aware Scheduler, FAJ 121 0859 is active.
				        Takes-effect: Cell lock/unlock";
				    yexte:dependencies "Only applicable if QoS Aware Scheduler, FAJ 121 0859 is active.";
				    yexte:takes-effect "Cell lock/unlock";
				}
				
				leaf srs-allocation-strategy {
				    type srs-allocation-strategy-type;
				    default deactivated;
				    description "If the leaf srs-allocation-strategy in the QoS configuration for a Data radio
				        Bearer assigned to a UE is set to activated, then an attempt is made to allocate
				        sounding for a UE. If several Data Radio Bearers are setup towards the UE with
				        different QoS configurations, and the QoS configurations has different
				        QCI parameter, an algorithm using the priority parameter in
				        the QoS configuration, will resolve which QoS configuration that
				        will define sounding
				        
				        Takes-effect: New connection";
				    yexte:takes-effect "New connection";
				}
				
				leaf ul-max-waiting-time {
                    type uint-500;
                    units "ms";
                    default 0;
                    description "The scheduler attempts to achieve ul-max-waiting-time for UL bearers
                        before giving any UL bearer a higher priority.
                        Value 0 means that the higher priority is never applied.
                        Must be set to a similar or slightly shorter value than the pdb.
                        Setting too low a value can affect other services with higher priority.
                        For more information about pdb refer to TS 23.203.
                        
                        Dependencies: Only used for Resource Fair Scheduling algorithm. Only applicable
                        if Advanced Differentiation for Resource Fair Scheduler, FAJ 121 4415 is active.
                        Disturbances: Changing this leaf can affect performance of all data bearers.
                        A value that is set too low can affect other services with higher priority.
                        A value that is set too high can cause Dynamic UE Admission Control to fail
                        in keeping the cell stable at overload.
                        Takes-effect: New connection";
                    yexte:dependencies "Only used for Resource Fair Scheduling algorithm. Only applicable
                        if Advanced Differentiation for Resource Fair Scheduler, FAJ 121 4415 is active.";
                    yexte:disturbances "Changing this leaf can affect performance of all data bearers.
                        A value that is set too low can affect other services with higher priority.
                        A value that is set too high can cause Dynamic UE Admission Control to fail
                        in keeping the cell stable at overload.";
                    yexte:takes-effect "New connection";
                }
				
				leaf ul-min-bit-rate {
                    type uint32 {
                        range "0..75000";
                    }
                    units "kbps";
                    default 0;
                    description "The scheduler will attempt to achieve minbitrate for all bearers
                        before giving any user a higher rate.
                        Value 0 means that the minRate scheduler is not used.
                        
                        Dependencies: This parameter will only be used if one of the following
                        Proportional Fair scheduling algorithms has been selected
                            - maximum-c-over-i
                            - proportional-fair-low
                            - proportional-fair-medium
                            - proportional-fair-high
                            - equal-rate.
                        Only applicable if QoS Aware Scheduler, FAJ 121 0859 is active.
                        Takes-effect: New connection";
                    yexte:dependencies "This parameter will only be used if one of the following
                        Proportional Fair scheduling algorithms has been selected
                            - maximum-c-over-i
                            - proportional-fair-low
                            - proportional-fair-medium
                            - proportional-fair-high
                            - equal-rate.
                        Only applicable if QoS Aware Scheduler, FAJ 121 0859 is active.";
                    yexte:takes-effect "New connection";
                }
				
			}
			
			list logical-channel-group {
			    key "id";
                min-elements 4;
                max-elements 4;
                description "Represents QoS configuration related to a Logical Channel group.";
                yexte:is-system-created;
                
                leaf id {
                    type uint8 {
                        range "0..3";
                    }
                    description "The values correspond to logical channel group IDs in 3GPP TS 36.321.";
                }
                
			}
		}

		container eutra-network {		
			description "This is a container for data related to EUTRA networks.";
			yexte:is-system-created;
				
			list external-enodeb-function {
				key "id";
				max-elements 512;
				description "Each entry represents an external enodeb.";

				leaf id {
					type string;
					description "A user friendly identifier for the external enodeb";
				}

				leaf enb-id {
					type uint32 {
						range "0..1048575";
					}
					mandatory true;
					description "The ID of an enodeb within a Public Land Mobile Network (PLMN).";
				}

				leaf es-cell-capacity-scaling {
				    type uint-100;
					units "percent";
					default 100;
					description "Scaling factor for secondary cell subscription capacity. Used to
						decrease carrier aggregation attraction of cells belonging to indicated
						enodeb if cell is used as external secondary cell for carrier aggregation.";
				}

				container enodeb-plmn-id {
					uses plmn-identity;
				}

				list external-eutran-cell-fdd {
					key "id";
					unique "local-cell-id";
					max-elements 24;
					description "Each list entry represents a neighbor EUTRAN cell (FDD)
						in another enodeb in any MME pool.";
					yexte:is-system-created;

					leaf id {
						type string;
						description "A user friendly identifier for the external cell";
					}

					leaf local-cell-id {
						type uint8;
						mandatory true;
						description "RBS internal ID for the external cell.
							Together with the Node ID and Public Land Mobile Network (PLMN) ID
							this is a globally unique eUTRAN Cell ID (ECGI).";
					}
				}
			}
		}

		list eutran-cell-fdd {
			key "id";
			unique "cell-id";
			max-elements 24;
			description "Each list entry represents an eutran cell and contains parameters needed by
				the cell. It also contains parameters for the mandatory common channels.";

			leaf id {
				type string;
				description "A user friendly identifier for the cell.";
			}

			leaf ul-channel-bandwidth {
				type channel-bandwidth-type;
				must '. = ../dl-channel-bandwidth' {
					description "This leaf is dependent on and shall be set to the same as
					    dl-channel-bandwidth.
					    
					    Note: The expression above is given only as guidance for northbound user.
					    Values supplied for this leaf are not validated by the adapter against
					    this expression.";
				}
				description "The uplink channel bandwidth in the cell
					
					Traffic disturbance: Changes may affect traffic.
					Takes effect: Object disabled/enabled.";
				yexte:disturbances "Changes may affect traffic.";
				yexte:takes-effect "Object disabled/enabled.";
			}

			leaf cell-subscription-capacity {
				type uint-1000000;
				default 1000;
				description "Normalized subscription capacity of the cell. The value
					represents the total capacity of the cell used for traffic
					load balancing purposes.
					
					Traffic disturbance: Low values reduce cell capacity.";
				yexte:disturbances "Low values reduce cell capacity.";
			}

			leaf cell-downlink-ca-capacity {
				type uint-1000000;
				default 0;
				description "Normalized downlink cell capacity available for use by
					carrier aggregation. The value is used to calculate the
					aggregated capacity of a UE:s possible aggregation
					possibilities, for example by the CA Aware IFLB feature.";
			}

			leaf dl-channel-bandwidth {
				type channel-bandwidth-type;
				must '. = ../ul-channel-bandwidth' {
					description "This leaf is dependent on and shall be set to the same as
					    ul-channel-bandwidth.
					    
					    Note: The expression above is given only as guidance for northbound user.
					    Values supplied for this leaf are not validated by the adapter against
					    this expression.";
				}
				description "The downlink channel bandwidth in the cell.
				
					Traffic disturbance: Changes may affect traffic.
					Takes effect: Object disabled/enabled.";
				yexte:disturbances "Changes may affect traffic.";
				yexte:takes-effect "Object disabled/enabled.";
			}

			leaf cell-id {
				type uint8;
				mandatory true;
				description "RBS internal ID for the eutran cell.
					Together with the Node ID and Public Land Mobile Network (PLMN)
					this is a universally unique cell ID.
					
					Traffic disturbance: Changing this leaf can cause loss of traffic.";
				ayexte:restricted;
				yexte:disturbances "Changing this leaf can cause loss of traffic.";
			}
			
			leaf ca-prio-threshold {
				type uint16;
				default 300;
				description "The threshold number of secondary cells configured using prioritized
					secondary cell selection. When the number of secondary cells configured for UEs
					connected in this primary cell is higher than ca-prio-threshold, all frequency
					carriers configured for carrier aggregation are assumed to have equal priority
					regardless of the configured values.
					Dependencies: Only applicable when
					/enodeb-function/carrier-aggregation-function/dynamic-s-cell-selection-method = prioritized.
					
					Takes effect: Next restart";
				yexte:dependencies "Only applicable when
                                         /enodeb-function/carrier-aggregation-function/dynamic-s-cell-selection-method = prioritized.";
				yexte:takes-effect "Next restart";
			}
			
			leaf earfcndl {
				type uint32 {
					range "0..17999 | 46590..262143";
				}
				mandatory true;
				description "The channel number for the central downlink frequency. The mapping from
					channel number to physical frequency for specified EUTRA bands is described in
					3GPP TS 36.104. The values that can be used depend on national, operator-specific
					frequency allocation as well as on the supported frequency bands in the RBS.

					Dependencies: This leaf is dependent on and set together with earfcnul.
					The earfcnul and earfcndl values are dependent and relate according to default
					EUTRA TX channel to RX channel separation as specified in 3GPP TS 36.101 for the
					EUTRA operating band and channel bandwidth of the cell.";
				ayexte:restricted;
				yexte:dependencies "This leaf is dependent on and set together with earfcnul.
					The earfcnul and earfcndl values are dependent and relate according to default
                    			EUTRA TX channel to RX channel separation as specified in 3GPP TS 36.101 for the
                    			EUTRA operating band and channel bandwidth of the cell.";
			}
			
			leaf earfcnul {
				type uint32 {
					range "0 | 18000..35999 | 46590..262143";
				}
				mandatory true;
				description "Channel number for the central UL frequency.
					The mapping from channel number to physical frequency for specified EUTRA bands
					is described in 3GPP TS 36.104. Values that can be used depend on national,
					operator-specific frequency allocation, as well as on the supported frequency
					bands of the RBS.
					Value 0 means that the UL channel number is N/A for the DL-only bands.

					Dependencies: This leaf is dependent on and set together with earfcndl.
					The earfcnul and earfcndl values are dependent and relate according to default
					EUTRA TX channel to RX channel separation as specified in 3GPP TS 36.101 for
					the EUTRA operating band and channel bandwidth of the cell.
				    
				    Traffic disturbance: Changes may affect traffic.
					Takes effect: Object disabled/enabled.";
				yexte:dependencies "This leaf is dependent on and set together with earfcndl.
					The earfcnul and earfcndl values are dependent and relate according to default
					EUTRA TX channel to RX channel separation as specified in 3GPP TS 36.101
					for the EUTRA operating band and channel bandwidth of the cell.";
				yexte:disturbances "Changes may affect traffic";
				yexte:takes-effect "Object disabled/enabled.";
			}
			
			leaf est-cell-cap-usable-fraction {
				type uint-100;
				units "percent";
				default 100;
				description "Scaling factor for the estimated cell subscription capacity.
					Can be used to reduce the traffic load balancing attraction of the cell.
					Used if traffic handling capacity of the cell is constrained by circumstances
					the Automated Cell Capacity Estimation feature is unable to capture.
					An example of such a circumstance is at limited UL capacity in a TDD cell.

					When the leaf value is set to 0, the corresponding cell uses the value
					cell-subscription-capacity as the Cell Subscription Capacity value for
				    the cell. This bypasses the automatically estimated Cell Subscription
				    Capacity value for the cell.
					
					Traffic disturbance: Changing this leaf can cause loss of traffic.";
				yexte:disturbances "Changing this leaf can cause loss of traffic.";
			}
			
			leaf lb-tp-non-qual-fraction {
				type uint8 {
					range "0 | 20..80";
				}
				units "0.01";
				default 35;
				description "The fraction of non-qualified UEs at UE selection for throughput aware
					load balancing. In case throughput aware UE selection is enabled, this parameter
					sets a target size for the fraction of UE to be disqualified for load balancing
					due to insufficient relative gain when moving UE from source to target cell.
					
					Special value 0 means that the throughput aware UE selection for this cell is
					disabled.";
			}
			
			leaf lb-tp-rank-thresh-min {
				type int8 {
					range "-100 | -60..60";
				}
				units "0.01";
				default "-20";	
				description "The minimum threshold for the relative gain at throughput aware load balancing.
					A negative value may allow for some throughput loss for the individual UE, if
					the load balancing criteria requires so. Higher values may increase the
					fraction of non-qualified UEs at UE selection for throughput aware load
					balancing and may cause the load balancing to stall.
					
					Special value -100 means the lower boundary for the threshold is disabled.
					
					Traffic disturbance: Changing this leaf can cause loss of traffic.";
				yexte:disturbances "Changing this leaf can cause loss of traffic.";
			}
			
			leaf ul-s-cell-priority {
				type uint8 {
					range "0..5";
				}
				default 5;
				description "Relative priority in initial secondary cell selection for cells
					that can be configured with UL Carrier Aggregation. Applicable where
					several secondary cells are initially configured simultaneously.
					Lowest value has highest priority.
					
					Takes effect: New connection";
				yexte:takes-effect "New connection";
			}
			
			leaf physical-layer-cell-id-group {
				type uint8 {
					range "0..167";
				}
				mandatory true;
				description "The physical layer cell ID group. Physical-layer cell IDs are grouped
					into 168 unique physical-layer cell-identity groups, each group containing
					3 unique subidentities.

					This leaf together with physical-layer-sub-cell-id is used to calculate
					physical layer cell ID (see 3GPP TS 36.211) that is sent as part of the
					system information (see 3GPP TS 36.331).
					
					Traffic disturbance: Changes may affect traffic";
				yexte:disturbances "Changes may affect traffic";
			}
			
			leaf physical-layer-sub-cell-id {
				type uint8 {
					range "0..2";
				}
				mandatory true;
				description "The subidentity within the physical layer cell ID group. Physical-layer
					cell IDs are grouped into 168 unique physical-layer cell-identity groups, each
					group containing 3 unique subidentities.

					This leaf together with physical-layer-cell-id-group is used to calculate
					physical layer cell ID (see 3GPP TS 36.211) that is sent as part of the
					system information (see 3GPP TS 36.331).
					
					Traffic disturbance: Changes may affect traffic";
				yexte:disturbances "Changes may affect traffic";
			}
			
			leaf tac {
                                type uint16;
				mandatory true;
				description "Tracking Area Code for the eutran cell.
					
					Traffic disturbance: Changes may affect traffic";
				yexte:disturbances "Changes may affect traffic";
			}
			
			leaf dl-configurable-frequency-start {
			    type uint-100;
			    default 0;
			    units "percent";
			    description "Specifies the start frequency offset for the allocation of resources
			        when the downlink interference management is disabled expressed as a percentage
			        of the configured bandwidth.
			        
			        Dependencies: dl-interference-management-active shall be disabled before
	                this parameter takes effect.
			        Takes-effect: Object unlocked";
			    yexte:dependencies "dl-interference-management-active shall be disabled before
			        this parameter takes effect.";
			    yexte:takes-effect "Object unlocked"; // Which object?
			}
			
			leaf dl-interference-management-active {
			    type boolean;
			    default false;
			    description "Specifies if the downlink interference management is enabled or disabled.
			        
			        Takes-effect: Object unlocked";
			    yexte:takes-effect "Object unlocked"; // Which object?
			}
			
			leaf ul-srs-enable {
			    type boolean;
			    default false;
			    description "This parameter controls whenever sounding shall be enabled or not for the
			        uplink frequency selective scheduling functionality.
			        
			        Dependencies: Only applicable when Uplink Frequency Selective Scheduling, FAJ 121 1799
                                is active.
			        Takes-effect: Cell lock/unlock";
			        yexte:dependencies "Only applicable when Uplink Frequency Selective Scheduling, FAJ 121 1799
                                is active.";
			    yexte:takes-effect "Cell lock/unlock";
			}

                        leaf-list sector-carrier-ref {
                            type leafref {
                                    path "/enodeb-function/sector-carrier/id";
                            }
                            max-elements 12;
                            description "Reference to sector-carrier list entries.

                                Traffic disturbance: Changes may affect traffic.
                                Takes effect: Object disabled/enabled.";
                            yexte:disturbances "Changes may affect traffic.";
                            yexte:takes-effect "Object disabled/enabled.";
                        }

                        leaf administrative-state {
                            type adm-state;
                            default "unlocked";
                            description "The administrative state.";
                        }

                        leaf operational-state {
                            type oper-state;
                            config false;
                            description "The operational state. This leaf is set by the application in the RBS";
                        }

                        leaf-list availability-status {
                            type avail-status;
                            config false;
                            description "The availability status. It contains details about
                                ../operational-state.
                                This leaf is set by the application in the RBS.";
                        }

			container ue-meas-control {
			    description "Models the manageable characteristics for UE measurements.";
				yexte:is-system-created;
				
				leaf s-measure {
					type int16 {
						range "-140..-44 | 0";
					}
					units "dBm";
					default 0;
					description "Primary cell quality threshold controlling whether
						or not the UE is required to perform measurements of intra-frequency,
						inter-frequency and inter-RAT neighboring cells.

						Value 0 indicates to disable s-Measure.

						Corresponds to s-Measure in TS 36.331.
						
						Traffic disturbance: High values can stop outgoing HO.
						Takes effect: New connection.";
					yexte:disturbances "High values can stop outgoing HO.";
					yexte:takes-effect "New connection.";
				}

			    container report-config-eutra-interfreq-lb {
					description "Contains the Report Configuration settings for UE measurements
						initiated for EUTRA Inter-frequency Load Balancing";
					yexte:is-system-created;

                    leaf a5-threshold1-rsrp {
                        type int16 {
                            range "-140..-44";
                        }
                        units "dBm";
                        default -44;
                        description "The Reference Signal Received Power (RSRP) threshold1 value for eventA5.
						
							Traffic disturbance: Changing this leaf can affect traffic";
						yexte:disturbances "Changing this leaf can affect traffic";
                    }

                    leaf a5-threshold2-rsrp {
                        type int16 {
                            range "-140..44";
                        }
                        units "dBm";
                        default -44;
                        description "The Reference Signal Received Power (RSRP) threshold2 value for eventA5.
						
							Traffic disturbance: Changing this leaf can affect traffic";
						yexte:disturbances "Changing this leaf can affect traffic";
                    }

                    leaf a5-threshold2-rsrq {
                        type int16 {
                         	range "-195..-30";
                        }
						units "0.1 dB";
						must '. mod 5 = 0' {
							description "The value must be set with resolution/step of 5
							    
							    Note: The expression above is given only as guidance for northbound user.
							    Values supplied for this leaf are not validated by the adapter against
							    this expression.";
						}
                        default -195;
                        description "The Reference Signal Received Quality (RSRQ) threshold2 value for eventA5.
						
							Traffic disturbance: Changing this leaf can affect traffic";
						yexte:disturbances "Changing this leaf can affect traffic";
                    }
					
                    leaf hysteresis-a5 {
                        type uint8 {
                         	range 0..150;
                        }
						units "0.1 dB";
						must '. mod 5 = 0' {
							description "The value can must set with resolution/step of 5
							    
							    Note: The expression above is given only as guidance for northbound user.
							    Values supplied for this leaf are not validated by the adapter against
							    this expression.";
						}
                        default 10;
                        description "The hysteresis value for the eventA5 measurement.
						
							Traffic disturbance: Changing this leaf can affect traffic";
						yexte:disturbances "Changing this leaf can affect traffic";
                    } 
			    }
			}
			
			list eutran-freq-relation {
				key "id";
				max-elements 9;
				description "This represents a mobility relation between an eutran cell and an eutran
					frequency. It contains parameters that are specific for the relation.";
				yexte:is-system-created;

				leaf id {
					type string;
					description "A user friendly identifier for the frequency relation";
				}
				
				leaf ca-freq-priority {
					type int8 {
						range "-1..7";
					}
					default 4;
					description "Prioritizes eutran frequency carriers from which to pick
						secondary cells for carrier aggregation.
						0 means lowest priority.
						-1 means the frequency is excluded from secondary cell selection. 
						
						Takes effect: New connection
					    
					    Dependencies: Only applicable when
					    /enodeb-function/carrier-aggregation-function/dynamic-s-cell-selection-method
					    = prioritized.
					    Can also be applied to dynamic-s-cell-selection-method = prioritized-automatic
					    as long as Configurable SCell Priority is licensed.";
					yexte:dependencies "Only applicable when
                        /enodeb-function/carrier-aggregation-function/dynamic-s-cell-selection-method = prioritized.
                        Can also be applied to dynamic-s-cell-selection-method = prioritized-automatic
                        as long as Configurable SCell Priority is licensed.";
					yexte:takes-effect "New connection";
				}
				
				leaf ca-freq-proportion {
					type uint-100;
					default 100;
					description "In conjunction with ca-prio-threshold the value sets a threshold for
						the number of secondary cells on this frequency carrier that can be configured
						using prioritized secondary cell selection. A normalized value is applied.
						When frequency carriers have same priority, secondary cells are selected on the
						carrier with the lowest proportional secondary cell utilization.
					    
					    Dependencies: Only applicable when
					    /enodeb-function/carrier-aggregation-function/dynamic-s-cell-selection-method
					    = prioritized.
						
						Takes effect: New connection";
					yexte:dependencies "Only applicable when
                        /enodeb-function/carrier-aggregation-function/dynamic-s-cell-selection-method = prioritized.";
					yexte:takes-effect "New connection";
				}

				leaf ca-triggered-redirection-active {
					type boolean;
					default true;
					description "Parameter used to specify whether or not CA triggered
						redirection is activated from the current cell towards a certain frequency.
						
						Traffic disturbance: Changing this leaf can affect traffic.
						Takes effect: New connection";
					yexte:disturbances "Changing this leaf can affect traffic.";
					yexte:takes-effect "New connection";
				}
				
				leaf lb-a5-thr1-rsrp-freq-offset {
					type uint-100;
					units "dB";
					default 0;
					description "The frequency-relation specific offset for the absolute threshold
						a5-threshold1-rsrp, RSRP threshold1 for event A5, used for Inter-frequency
						load balancing.
						
						Takes effect: Ongoing connection";
					yexte:takes-effect "Ongoing connection";
				}
				
				leaf lb-activation-threshold {
					type uint-1000;
					units "0.001";
					default 0;
					description "The minimum target cell load (subscription ratio) the source cell takes into
						account when determining the amount of load balancing action to a cell
						using this carrier frequency.";
				}
				
				leaf q-offset-freq {
				    type offset-freq-type;
				    default 0;
				    description "Frequency specific offset for E-UTRAN frequencies used in connected mode.
				        In idle mode,  the negative value of this offset is used.
				        Specification: 3GPP TS 36.331";
				}

				list eutran-freq-to-qci-profile-relation {
					key "qci-profile-ref";
					max-elements 19;
					description "Encapsulates parameters for service specific load 
						management for a certain QCI profile."; // Represented as sequence in ECIM, not possible to edit only 1 value

					leaf lb-qci-profile-handling {
						type lb-qci-profile-handling-type;
						default "allowed";
						description "Specifies QCI profile handling with regard to load management.";
					}

					leaf qci-profile-ref {
						type instance-identifier;
						must 're-match(.,"/.*enodeb-function/.*qci-table/(.*qci-profile-predefined\[.*id=.+\]|.*qci-profile-operator-defined\[.*id=.+\])")' {
							description "The instance identifier must point at a qci-profile-predefined or
								qci-profile-operator-defined list entry
								
								Examples of valid values are
								/lrtadpt:enodeb-function/lrtadpt:qci-table/lrtadpt:qci-profile-predefined[lrtadpt:id='qci9']
								/lrtadpt:enodeb-function/lrtadpt:qci-table/lrtadpt:qci-profile-operator-defined[lrtadpt:id='myQci10']
							    
							    Note: The expression above is given only as guidance for northbound user.
							    Values supplied for this leaf are not validated by the adapter against
							    this expression.";
						}
						description "Refers to a qci-profile-predefined or
							qci-profile-operator-defined list entry.";
					}
				}

				list eutran-cell-relation {
					key "id";
					max-elements 128;
					description "Each entry represents the handover relationship between two neighboring
						eutran cells.";
						
					leaf coverage-indicator {
						type supported-coverage-type;
						default "none";	
						description "Indicates whether the coverage area of the cell indicated by the relation
							has approximately the same coverage area (overlap) as this cell, or whether
							it fully covers this cell, or if it is fully contained in this cell.
							
							Traffic disturbance: Changes may affect traffic.";
						yexte:disturbances "Changes may affect traffic.";
					}
					
					leaf id {
						type string;
						description "A user friendly identifier for the cell relation";
					}

					leaf neighbor-cell-ref {
						type instance-identifier;
						must 're-match(.,"/.*enodeb-function/.*eutran-cell-fdd\[.*id=.+\]|/.*enodeb-function/.*eutra-network/.*external-enodeb-function\[.*id=.+\]/.*external-eutran-cell-fdd\[.*id=.+\]")' {
							description "The instance identifier must point at an entry in eutran-cell-fdd list or
								the external-eutran-cell-fdd list
							
								Examples of valid values are
								/lrtadpt:enodeb-function/lrtadpt:eutran-cell-fdd[lrtadpt:id='myCell']
								/lrtadpt:enodeb-function/lrtadpt:eutra-network/lrtadpt:external-enodeb-function[lrtadpt:id='extEnb1']/lrtadpt:external-eutran-cell-fdd[lrtadpt:id='extCell1']
							    
							    Note: The expression above is given only as guidance for northbound user.
                                Values supplied for this leaf are not validated by the adapter against
                                this expression.";
						}
						mandatory true;
						description "Reference to an entry in eutran-cell-fdd list or
							the external-eutran-cell-fdd list";
						ayexte:restricted;
					}

					leaf load-balancing {
						type load-balancing-type;
						default "not-allowed";
						description "This leaf indicates whether Inter-Frequency Load Balancing is ALLOWED or
							NOT-ALLOWED or if Inter-Frequency Offload shall be applied from the current cell
							to the cell indicated by the cell relation.";
					}
					
					leaf s-cell-candidate {
						type s-cell-candidate-type;
						default "auto";
						description "Secondary cell candidate status.
							The value indicates whether the cell indicated by parameter neighbor-cell-ref
							can be used as secondary cell for UEs using this cell as their primary cell.
							The secondary cell can be either local to the eNodeB, or on a remote eNodeB.
							
							Takes effect: Next secondary cell configuration during the ongoing connection.";
						yexte:takes-effect "Next secondary cell configuration during the ongoing connection.";
					}
					
					leaf s-cell-priority {
						type int8 {
							range "-1..7";
						}
						default 7;
						description "Used for selecting a secondary cell within a frequency carrier.
							The secondary cell with highest priority is selected during initial blind
							secondary cell selection.
							0 means lowest priority.
							-1 means the cell is excluded from blind secondary cell selection.
						    
						    Dependencies: Only applicable when
						    /enodeb-function/carrier-aggregation-function/dynamic-s-cell-selection-method
						    = prioritized.
							
							Takes effect: New connection";
						yexte:dependencies "Only applicable when
                            /enodeb-function/carrier-aggregation-function/dynamic-s-cell-selection-method = prioritized.";
						yexte:takes-effect "New connection";
					}
					
					leaf cell-individual-offset-eutran {
					    type offset-freq-type;
					    default 0;
					    description "Offset value for the neighbor cell. Used when UE is in connected mode.
					        This leaf can be modified by SON functions.
					        
					        Takes effect: New connection";
					    yexte:takes-effect "New connection";
					}
					
					leaf q-offset-cell-eutran {
					    type offset-freq-type;
					    default 0;
					    description "Offset value applied to a specific cell in idle mode mobility state.";
					}
				}
			}
		}

		container load-balancing-function {
			must 'lb-diff-ca-offset > lb-threshold' {
				description "lb-diff-ca-offset must be greater than lb-threshold
				    
				    Note: The expression above is given only as guidance for northbound user.
				    Values supplied for this leaf are not validated by the adapter against
				    this expression.";
			}
			description "Contains parameters and constraints for Idle Mode Load Balancing functions";
			yexte:is-system-created;

			leaf lb-threshold {
				type uint-1000;
				units "0.001";
				default 30;
				description "The minimum load (subscription ratio) difference to trigger
					load balancing action.
					
					Traffic disturbance: Changing this leaf can cause loss of traffic.";
				yexte:disturbances "Changing this leaf can cause loss of traffic.";
			}

			leaf lb-ceiling {
				type uint16 {
					range "10..2000";
				}
				units "0.001";
				default 200;
				description "The maximum load (subscription ratio) difference taken into
					account in load balancing action.
					
					Traffic disturbance: Changing this leaf can cause loss of traffic.";
				yexte:disturbances "Changing this leaf can cause loss of traffic.";
			}

			leaf lb-rate-offset-coefficient {
				type uint-1000;
				units "0.001";
				must '. mod 20 = 0' {
					description "The value must be set with resolution/step of 20
					    
					    Note: The expression above is given only as guidance for northbound user.
					    Values supplied for this leaf are not validated by the adapter against
					    this expression.";
				}
				default 320;
				description "Coefficient of rate-dependent load balancing offset.
					Moderates how much the load balancing must be offset 
					towards a cell with higher capacity.
					
					Traffic disturbance: Changing this leaf can cause loss of traffic.";
				yexte:disturbances "Changing this leaf can cause loss of traffic.";
			}

			leaf lb-rate-offset-load-threshold {
				type uint-16000;
				units "0.001";
				default 500;
				description "Specifies the threshold for the source and target cell
					average load, above which the rate offset is set to zero.
					
					Traffic disturbance: Changing this leaf can affect traffic.";
				yexte:disturbances "Changing this leaf can affect traffic.";
			}

			leaf lb-ca-threshold {
				type uint-16000;
				units "0.001";
				default 800;	
				description "The maximum load in the target cell in order to redirect a CA 
					capable UE to that target cell. The maximum load in the current cell in order 
					to apply the capacity criterion when load balancing a CA capable UE.
					
					Traffic disturbance: Changing this leaf can affect traffic.
					Takes effect: New connection";
				yexte:disturbances "Changing this leaf can affect traffic.";
				yexte:takes-effect "New connection";
			}

			leaf lb-diff-ca-offset {
				type uint-1000;
				units "0.001";
				default 100;
				description "The maximum load difference between the target cell and the source 
					cell in order to redirect a CA capable UE to that target cell. The maximum load 
					difference between the source cell and the target cell in order to apply the 
					capacity criterion when load balancing a CA capable UE.
					
					Traffic disturbance: Changing this leaf can affect traffic.
					Takes effect: New connection";
				yexte:disturbances "Changing this leaf can affect traffic.";
				yexte:takes-effect "New connection";
			}

			leaf lb-ca-cap-hysteresis {
				type uint-100;
				units "0.01";
				default 20;
				description "Capacity related hysteresis value considered when checking the 
					capacity criterion for both load balancing of CA capable UEs and CA triggered 
					redirection.
					
					Traffic disturbance: Changing this leaf can affect traffic.
					Takes effect: New connection";
				yexte:disturbances "Changing this leaf can affect traffic.";
				yexte:takes-effect "New connection";
			}
			
		}

		container carrier-aggregation-function {
			description "Contains parameters and constraints for the Carrier Aggregation function";
			yexte:is-system-created;

			leaf ca-usage-limit {
				type uint16;
				units "1 UE SCell instances";
				default 65535;
				description "The value configures the number of secondary cell connections which
					can be in use for carrier aggregation. A secondary cell costs in memory
					the same as a primary cell for each UE. It is preferred to avoid limiting
					secondary cell connections with ca-usage-limit, and use ca-preemption-threshold
					instead.
					
					Takes effect: Next restart";
				yexte:takes-effect "Next restart";
			}

			leaf ca-preemption-threshold {
				type uint-100;
				units "percent";
				default 50;
				description "Configures the resource consumption margin in percentage,
					beyond which secondary cells shall not be configured.
					
					Takes effect: Next restart";
				yexte:takes-effect "Next restart";
			}

			leaf s-cell-act-deact-data-thres {
				type int16 {
					range "-1..5000";
				}
				units "0.1 Number of DL subframes";
				default 100;
				description "One or more secondary cells can be activated if minimum time needed
					to transmit all bits in all priority queues of UE is higher than
					s-cell-act-deact-data-thres. When deciding the activation of one secondary
					cell, minimum time needed to transmit all bits is calculated as the number
					of bits in all priority queues, divided by the number of bits that can be
					transmitted in one TTI by all active serving cells prior to activation
					decision. This is computed as though the UE is given all resources in those
					cells. If the condition for activating one secondary cell is satisfied,
					a second secondary cell is also considered for activation but the minimum time
					needed to transmit all bits is now calculated by considering the added capacity
					of the first new secondary cell that is already considered for activation.
					
					For FDD, the unit number of DL subframes is equivalent to ms, but for TDD UL/DL
					subframe configuration 1, there are 6 DL subframes in 10ms, and for UL/DL
					subframe configuration 2, there are 8 DL subframes in 10ms.
					
					-1 means the data-triggered activation condition is always satisfied even with
					no data in the buffer, and also that the data-triggered deactivation condition
					is never satisfied.
					
				    Dependencies: s-cell-act-deact-data-thres-hyst <= s-cell-act-deact-data-thres
				    when s-cell-act-deact-data-thres is not equal to -1
				    
					Takes effect: Cell lock/unlock";
				yexte:dependencies "s-cell-act-deact-data-thres-hyst <= s-cell-act-deact-data-thres
                    when sCellActDeactDataThres is not equal to -1";
				yexte:takes-effect "Cell lock/unlock";
			}
			
			leaf s-cell-act-deact-data-thres-hyst {
				type uint-5000;
				units "0.1 Number of DL subframes";
				default 90;
				description "If the minimum time needed to transmit all bits in all priority queues
					of a UE is less than or equal to s-cell-act-deact-data-thres minus
					s-cell-act-deact-data-thres-hyst, then deactivation of one component carrier
					is considered.
					
					Minimum time needed to transmit all bits is calculated as number of bits in all
					priority queues, divided by the  number of bits that can be transmitted in one
					TTI by all active serving cells after deactivation decision. This is computed
					as though the UE is given all resources in those cells.
					
					For FDD, the unit number of DL subframes is equivalent to ms, but for TDD UL/DL
					subframe configuration 1, there are 6 DL subframes in 10ms, and for UL/DL
					subframe configuration 2, there are 8 DL subframes in 10ms.
					
					If s-cell-act-deact-data-thres is set to -1, the data-triggered deactivation
					condition is never satisfied and the value of s-cell-act-deact-data-thres-hyst
					is ignored.
				    
				    Dependencies: s-cell-act-deact-data-thres-hyst <= s-cell-act-deact-data-thres
				    when s-cell-act-deact-data-thres is not equal to -1
					
					Takes effect: Cell lock/unlock";
				yexte:takes-effect "Cell lock/unlock";
			}

			leaf s-cell-schedule-sinr-thres {
				type int16 {
					range "-200..300";
				}
				units "0.1 dB";
				default 0;
				description "No data is scheduled on secondary cell if wideband SINR is lower 
					than s-cell-schedule-sinr-thres. If SINR remains below threshold, secondary
					cell is deactivated when s-cell-deact-out-of-coverage-timer expired.
					
					Takes effect: Cell lock/unlock";
				yexte:takes-effect "Cell lock/unlock";
			}

			leaf wait-for-ca-opportunity {
				type int32 {
					range "-1..60000";
				}
				units "ms";
				default 10000;
				description "Controls the length of time that elapses until a UE is considered once
					again for secondary cell configuration after the eNB was not able to configure
					this UE with a suitable secondary cell.
					
					-1 means wait forever.
					
					Traffic disturbance: Extreme settings can turn off CA for the eNB.
					
					Changed value may take effect related to the next secondary cell configuration
					during the ongoing connection.";
				yexte:disturbances "Extreme settings can turn off CA for the eNB.";
				yexte:takes-effect "Ongoing connection";
			}

			leaf wait-for-better-s-cell-rep {
				type int16 {
					range "-1..32000";
				}
				units "ms";
				default 1000;
				description "Controls the length of time a UE searches for secondary cells
					on a particular frequency, or set of frequencies based on measurements
					when it is in poor secondary cell coverage.
					
					-1 means wait forever.
					
					Changed value can take effect related to the next secondary cell configuration
					during the ongoing connection.";
				yexte:takes-effect "Ongoing connection.";
			}

			leaf wait-for-additional-s-cell-opportunity {
				type int32 {
					range "-1..60000";
				}
				units "ms";
				default 10000;
				description "Controls the length of time that elapses until a UE is reconsidered for
					additional secondary cell configuration after the eNB was unable to configure
					this UE with more than one secondary cell.
					
					-1 means wait forever.
					
					Changed value can take effect related to the next secondary cell configuration
					during the ongoing connection.";
				yexte:takes-effect "Ongoing connection.";
			}
			
			leaf ca-rate-adjust-coeff {
				type uint8 {
					range "0..10";
				}
				default 10;
				description "Used to adjust factor of CC rate for CA UEs, which is used in scheduler's
					proportional fairness algorithm. A smaller value gives CA UE a greater
					advantage over non-CA UE.
					
					Value 0 sets rate as 0 and this is for testing purpose only.
					Values 1 - 4 set the rate as fraction of the cell rate in increased order.
					Value 5 sets cell based rate.
					Values 6 - 9 set the rate as cell rate plus rate influence from other 
					CCs in increased order.
					Value 10 sets the rate as aggregated rate of all CCs.
					
					Takes effect: Cell lock/unlock";
				yexte:takes-effect "Cell lock/unlock";
			}

			leaf s-cell-act-deact-ul-data-thresh {
				type uint-5000;
				units "0.1 Number of UL subframes";
				default 100;
				description "If the minimum time needed to transmit all bits in all priority queues
					in UL of a UE is higher than s-cell-act-deact-ul-data-thresh, activation
					of one or more secondary cells is considered.
				    
				    Dependencies: s-cell-act-deact-ul-data-thresh-hyst =<
				    s-cell-act-deact-ul-data-thresh
					
					Takes effect: Cell lock/unlock";
				yexte:dependencies "s-cell-act-deact-ul-data-thresh-hyst =< s-cell-act-deact-ul-data-thresh";
				yexte:takes-effect "Cell lock/unlock";
			}

			leaf s-cell-act-deact-ul-data-thresh-hyst {
				type uint-5000;
				units "0.1 Number of UL subframes";
				default 90;
				description "If minimum time needed to transmit all bits in all priority queues in UL of
					a UE is less than s-cell-act-deact-ul-data-thresh minus
					s-cell-act-deact-ul-data-thresh-hyst, deactivation of one CC is considered.
				    
				    Dependencies: s-cell-act-deact-ul-data-thresh-hyst =<
				    s-cell-act-deact-ul-data-thresh
					
					Takes effect: Cell lock/unlock";
				yexte:dependencies "s-cell-act-deact-ul-data-thresh-hyst =< s-cell-act-deact-ul-data-thresh";
				yexte:takes-effect "Cell lock/unlock";
			}

			leaf pdcch-enhanced-la-for-volte {
				type boolean;
				default false;
				description "Enables CA when VoIP and enhanced PDCCH Link Adaptation on
					FDD primary cell are both active. Not used for TDD primary cells.
					
					Dependencies: Only applicable when Carrier Aggregation, FAJ 121 3046 and
					Enhanced PDCCH Link Adaptation, FAJ 121 3051 are active, and a VoIP bearer
					exists for a UE.
					
					Takes effect: At the next initial secondary cell selection during the
					ongoing connection";
				yexte:dependencies "Only applicable when Carrier Aggregation, FAJ 121 3046 and
                    Enhanced PDCCH Link Adaptation, FAJ 121 3051 are active, and a VoIP bearer
                    exists for a UE.";
				yexte:takes-effect "At the next initial secondary cell selection during the ongoing connection";
			}

			leaf s-cell-selection-mode {
				type s-cell-selection-mode-type;
				default "ack-sequential-scell-selection";	
				description "Selects the behavior of selecting secondary cell candidates
					beyond the first candidate.
					
					Warning: There is a risk when using un-ack-simultaneous-scell-selection that
					the UE may not report a bad secondary cell.
					
					Dependencies: Only applicable when
					Dynamic SCell Selection for Carrier Aggregation, FAJ 121 3063 and
					3CC DL Carrier Aggregation Extension, FAJ 121 3084 are active.
					
					Takes effect: New connection";
				yexte:dependencies "Only applicable when
                    Dynamic SCell Selection for Carrier Aggregation, FAJ 121 3063 and
                    3CC DL Carrier Aggregation Extension, FAJ 121 3084 are active.";
				yexte:takes-effect "New connection";
			}

			leaf s-cell-act-prohibit-timer {
				type uint-5000;
				units "ms";
				default 10;
				description "Activation prohibit timer. No new secondary cell activation is
					allowed while this timer is running.
					
					Takes effect: Cell lock/unlock";
				yexte:takes-effect "Cell lock/unlock";
			}

			leaf s-cell-deact-prohibit-timer {
				type uint-5000;
				units "ms";
				default 200;
				description "Deactivation prohibit timer. No new secondary cell deactivation
					is allowed while this timer is running.
					
					Takes effect: Cell lock/unlock";
				yexte:takes-effect "Cell lock/unlock";
			}

			leaf s-cell-deact-out-of-coverage-timer {
				type int16 {
					range "-1..5000";
				}
				units "ms";
				default 100;
				description "Secondary cell is deactivated if:
					- wideband DL SINR remains below s-cell-schedule-sinr-thres, or
					- no Channel State Information is received by the eNB for a duration of
					s-cell-deact-out-of-coverage-timer.
					
					Deactivation can be deferred, for example by s-cell-deact-prohibit-timer.
					
					-1 means the secondary cell is not deactivated due to the SINR condition.";
			}

			leaf s-cell-deact-delay-timer {
				type uint-5000;
				units "ms";
				default 50;
				description "One secondary cell is deactivated if minimum time needed to transmit
					all bits in all priority queues of a UE is less than or equal to
					s-cell-act-deact-data-thres minus s-cell-act-deact-data-thres-hyst for
					a duration of s-cell-deact-delay-timer.
				    
				    Dependencies: s-cell-act-deact-data-thres-hyst <= s-cell-act-deact-data-thres";
				yexte:dependencies "s-cell-act-deact-data-thres-hyst <= s-cell-act-deact-data-thres";
			}

			leaf dynamic-s-cell-selection-method {
				type dynamic-s-cell-selection-method-type;
				default "round-robin";
				description "Method used to select secondary cell candidates.
				
					Dependencies: Only applicable when feature Dynamic SCell Selection
					for Carrier Aggregation, FAJ 121 3063 and feature
					Configurable SCell Priority, FAJ 121 4701 and/or
					feature Automatic SCell Priority, FAJ 121 4734 are active.
					
					Takes effect: New connection";
				yexte:dependencies "Only applicable when feature Dynamic SCell Selection
                    for Carrier Aggregation, FAJ 121 3063 and feature
                    Configurable SCell Priority, FAJ 121 4701 and/or
                    feature Automatic SCell Priority, FAJ 121 4734 are active.";
				yexte:takes-effect "New connection";
			}

			leaf ca-preference {
				type ca-preference-type;
				default "none";
				description "Preference between downlink and uplink carrier aggregation.
				
					Dependencies: Only applicable when 3CC Carrier aggregation Extension
					Feature, FAJ 121 3084 is active and s-cell-selection-mode is equal to
				    un-ack-simultaneous-scell-selection or ack-simultaneous-scell-selection.
					
					Takes effect: New connection";
				yexte:dependencies "Only applicable when 3CC Carrier aggregation Extension
                    Feature, FAJ 121 3084 is active and s-cell-selection-mode is equal to
                    un-ack-simultaneous-scell-selection or ack-simultaneous-scell-selection.";
				yexte:takes-effect "New connection";
			}

			leaf enhanced-selection-of-mimo-and-ca {
				type boolean;
				default false;
				description "Used to enable enhanced selection of four layer MIMO and carrier
					aggregation. Secondary cell is not added if effective bandwidth is reduced.
					If effective bandwidth is not changed, tie-breaking rule is governed by
					fourLayerMimoPreferred. Effective bandwidth includes the number of PRBs and
					MIMO layer capability of the UE in all serving cells.
					
					Dependencies: Only applicable when Configurable SCell Priority, FAJ 121 4701
					is active.
					
					Takes effect: New connection";
				yexte:dependencies "Only applicable when Configurable SCell Priority, FAJ 121 4701
                    is active.";
				yexte:takes-effect "New connection";
			}

			leaf four-layer-mimo-preferred {
				type boolean;
				default false;
				description "Whether or not secondary cell is added when there is no change in
					effective bandwidth. Applies when enhanced selection of four layer MIMO and
					carrier aggregation is enabled. If set to true, secondary cell is not added,
					otherwise secondary cell is added.
					
					Dependencies: Only applicable when Configurable SCell Priority, FAJ 121 4701
					is active.
					
					Takes effect: New connection";
				yexte:dependencies "Only applicable when Configurable SCell Priority, FAJ 121 4701
                    is active.";
				yexte:takes-effect "New connection";
			}

		}

        list sector-carrier {
            key "id";
            max-elements 48;
            description "This container represents the power and frequency usage of the
                sector-equipment-function that covers an area.";

            leaf id {
                type "string";
                description "A user friendly identifier for the sector carrier.";
            }

            leaf-list availability-status {
                type avail-status; // non-unique
                config false;
                description "The availability status. It contains details about operational state.
                    This leaf-list is set by the application in the eNodeB.

                    Traffic disturbance: Changes may affect traffic.";
                yexte:disturbances "Changes may affect traffic";
            }

            leaf operational-state {
                type oper-state;
                config false;
                description "The operational state. This leaf is set by the application in the eNodeB.

                    Traffic disturbance: Changes may affect traffic.";
                yexte:disturbances "Changes may affect traffic";
            }

            leaf sector-function-ref {
                type leafref {
                    path "/rsefadpt:node-support/rsefadpt:sector-equipment-function/rsefadpt:id";
                }
                mandatory true;
                description "Reference to an entry in sector-equipment-function list.";
                ayexte:restricted;
            }

            leaf no-of-rx-antennas {
                type uint8 {
                    range "0 | 1 | 2 | 4 | 8";
                }
                default 0;
                description "Number of antennas that the sector-carrier uses for UL transmission.
                    When there are sector carriers with different number of RX antennas in the node,
                    set the leaf explicitly to the number of RX antennas that the
                    sector-carrier uses.
                    If parameter is set to 0, and optional features enabling usage of RX antennas
                    are deactivated, then the sector-carrier uses two RX branches.
                    If parameter is set to 0, and optional features enabling usage of RX antennas
                    are activated, then the sector-carrier uses the maximum number of RX antennas
                    defined by the operable features.

                    Dependencies: Dependent on optional features that enable usage of multiple
                    Rx antennas.
                    Traffic disturbance: Changes may affect traffic.
                    Takes-effect: Cell lock/unlock";
                yexte:dependencies "Dependent on optional features that enable usage of multiple
                    Rx antennas.";
                yexte:disturbances "Changes may affect traffic";
                yexte:takes-effect "Cell lock/unlock";
            }

            leaf no-of-tx-antennas {
                type uint8 {
                    range "0 | 1 | 2 | 4 | 8";
                }
                default 0;
                description "Number of antennas that the sector-carrier uses for DL transmission.
                    When there are sector carriers with different number of TX antennas in the node,
                    set the parameter explicitly to the number of TX antennas that the
                    sector-carrier uses.
                    If parameter is set to 0, and optional features enabling usage of TX antennas
                    are deactivated, then the sector-carrier uses one TX branch.
                    If parameter is set to 0, and optional features enabling usage of TX antennas
                    are activated, then the sector-carrier uses the maximum number of TX antennas
                    defined by the operable features.

                    Dependencies: Dependent on optional features that enable usage of multiple
                    Tx antennas.
                    Traffic disturbance: Changes may affect traffic.
                    Takes-effect: Cell lock/unlock";
                yexte:dependencies "Dependent on optional features that enable usage of multiple
                    Tx antennas.";
                yexte:disturbances "Changes may affect traffic";
                yexte:takes-effect "Cell lock/unlock";
            }

            leaf maximum-transmission-power {
                type int16 {
                    range "-1..1200";
                }
                units "0.1 dBm";
                config false;
                description "Maximum possible power at the antenna reference point, for all downlink
                    channels in all TX branches used simultaneously in the sector carrier.
                    -1 is used as an undefined value.

                    Note: Setting ../configured-max-tx-power has an impact on this leaf.
                    See Radio Network Configuration user guide 11/1553-HSC 105 50/1.";
            }

            leaf prs-enabled {
                type boolean;
                default true;
                description "If true, the Positioning Reference Signal is sent from this sector carrier.
                    1: For indoor antennas at the same location, if the sector carriers are
                       isolated, set prs-enabled to true for all sector carriers.
                       Transmission of PDSCH on the PRS subframe is not scheduled.
                    2: For combined macro and pico sector carriers, set prs-enabled to true for the
                       macro sector only. The other sector or sectors have prs-enabled = false.
                       However, transmission of PDSCH is still not scheduled on the same subframe
                       to prevent undesirable interferences.
                    Note: To reclaim PRS subframe for PDSCH transmission, OTDOA Supl license state
                    must be set to disabled.

                    Traffic disturbance: Changes may affect traffic.
                    Takes-effect: Object disabled/enabled";
                yexte:disturbances "Changes may affect traffic";
                yexte:takes-effect "Object disabled/enabled";
            }

            leaf ul-forced-timing-advance-command {
                type uint8 {
                    range "0..10";
                }
                units "0.52 microsecond";
                default 0;
                description "Forced additional value for Timing Advance Command in Random Access Response
                    according to 3GPP TS 36.213.

                    Takes-effect: Cell lock/unlock";
                reference "3GPP TS 36.213";
                yexte:takes-effect "Cell lock/unlock";
            }

            leaf no-of-muted-tx-antennas {
                type uint8 {
                    range "0..7";
                }
                config false;
                description "Number of muted Tx antennas when MIMO sleep mode is activated.";
            }

            leaf radio-transmit-performance-mode {
                type radio-operating-mode;
                default "default";
                description "A desired radio transmit operating mode, which is tailored to achieve good
                    throughput performance for a given highest modulation in downlink.

                    Takes-effect: Cell lock/unlock";
                yexte:takes-effect "Cell lock/unlock";
            }

            leaf configured-max-tx-power {
                type uint32 {
                    range "0..10000000";
                }
                units "mW";
                default "20000";
                description "Maximum output power to be used in a sector-carrier. The output power
                    is evenly distributed over antenna connectors used for TX transmission allocated
                    for the sector-carrier.

                    Value 0 must not be used.
                    To prevent the cell from transmitting, it must be locked.

                    Traffic disturbance: Changing this leaf can affect traffic
                    Precondition: Leaf can be set only when cell is locked.
                    Takes-effect: Object unlocked";
                reference "3GPP TS 28.658";
                yexte:disturbances "Changing this leaf can affect traffic";
                yexte:precondition "Leaf can be set only when cell is locked.";
                yexte:takes-effect "Object unlocked";
            }

            leaf tx-power-persistent-lock {
                type boolean;
                default false;
                description "Indicates if leaf configured-max-tx-power is locked or not.
                    When true, leaf configured-max-tx-power cannot be changed and parent data node
                    cannot be deleted.

                    Note: This leaf is only intended to be used on mRBS and mRRU.

                    Precondition: Once set to true there is no possibility to change the value
                    back to false unless a node re-integration is performed.";
                yexte:precondition "Once set to true there is no possibility to change the value
                    back to false unless a node re-integration is performed.";
            }

            container dl-calibration-data {
                config false;
                description "Downlink antenna calibration information.";

                leaf-list dl-calibration-supported-methods {
                    type dl-calibration-method;
                    max-elements 2;
                    description "Describes which types of downlink antenna calibration are supported.
                        An empty list means there is no support.";
                }

                leaf dl-calibration-active-method {
                    type dl-calibration-method;
                    description "Describes which downlink antenna calibration method is active (if any).

                        Dependencies: If ../dl-calibration-supported-methods is empty then the value of
                        dl-calibration-active-method will be 0 (none).";
                    yexte:dependencies "If ../dl-calibration-supported-methods is empty then the value of
                        dl-calibration-active-method will be 0 (none).";
                }

                leaf dl-calibration-status {
                    type dl-calibration-status-type;
                    description "Describes the current downlink antenna calibration status.

                        Dependencies: If ../dl-calibration-supported-methods is empty then the value of
                        dl-calibration-status will be 0 (inactive).";
                    yexte:dependencies "If ../dl-calibration-supported-methods is empty then the value of
                        dl-calibration-status will be 0 (inactive).";
                }
            }

            list rf-branch-rx-ref {
                key "rf-branch-rx-antenna-unit-group-ref rf-branch-rx-rf-branch-ref";
                max-elements 8;
                description "Each list entry contains a pair of leafrefs which uniquely identify the
                    rf-branch list entries whose RF ports are to be used for RX carrier allocations for
                    this particular sector-carrier. If no rf-branch-rx-ref list entries are configured,
                    allocation is based on the rf-branch MOM list (default behavior).

                    Disturbances: Modifying this list requires blocking and deblocking the cell.
                    Takes effect: List entry unlocked.
                    Precondition: Locked cell.";
                yexte:disturbances "Modifying this list requires blocking and deblocking the cell.";
                yexte:takes-effect "List entry unlocked.";
                yexte:precondition "Locked cell.";

                leaf rf-branch-rx-antenna-unit-group-ref {
                    type leafref {
                        path "/reqeqadpt:equipment/reqantadpt:antenna-unit-group/reqantadpt:id";
                    }
                    description "The key value of the antenna-unit-group list entry which is contains the
                        referenced rf-branch list entry.";
                }

                leaf rf-branch-rx-rf-branch-ref {
                    type leafref {
                        path "/reqeqadpt:equipment/reqantadpt:antenna-unit-group[reqantadpt:id=current()/../rf-branch-rx-antenna-unit-group-ref]/reqantadpt:rf-branch/reqantadpt:id";
                    }
                description "The key value of the referenced rf-branch list entry";
                }
            }


            list rf-branch-tx-ref {
                key "rf-branch-tx-antenna-unit-group-ref rf-branch-tx-rf-branch-ref";
                max-elements 8;
                description "Each list entry contains a pair of leafrefs which uniquely identify the
                    rf-branch list entries whose RF ports are to be used for TX carrier allocations for
                    this particular sector-carrier. If no rf-branch-tx-ref list entries are configured,
                    allocation is based on the rf-branch MOM list (default behavior).

                    Disturbances: Modifying this list requires blocking and deblocking the cell.
                    Takes effect: List entry unlocked.
                    Precondition: Locked cell.";
                yexte:disturbances "Modifying this list requires blocking and deblocking the cell.";
                yexte:takes-effect "List entry unlocked.";
                yexte:precondition "Locked cell.";

                leaf rf-branch-tx-antenna-unit-group-ref {
                    type leafref {
                        path "/reqeqadpt:equipment/reqantadpt:antenna-unit-group/reqantadpt:id";
                    }
                    description "The key value of the antenna-unit-group list entry which is contains the
                        referenced rf-branch list entry.";
                }

                leaf rf-branch-tx-rf-branch-ref {
                    type leafref {
                        path "/reqeqadpt:equipment/reqantadpt:antenna-unit-group[reqantadpt:id=current()/../rf-branch-tx-antenna-unit-group-ref]/reqantadpt:rf-branch/reqantadpt:id";
                    }
                description "The key value of the referenced rf-branch list entry";
                }
            }
        }
    }
}
